/*
* (C)2019 Lumina Networks, Inc.
* 2077 Gateway Place, Suite 500, San Jose, CA 95110.
* All rights reserved.
*
* Use of the software files and documentation is subject to license terms.
*/
module unified-inventory {
    yang-version 1;
    namespace "urn:opendaylight:unified-inventory";
    prefix "uni-inventory";

    import network-topology { prefix "nt"; revision-date 2013-10-21; }
    import ldk-device-database { prefix ldk-db; revision-date 2016-06-08; }

    revision 2019-04-04 {
        description "Initial revision";
    }

    description
        "Unified inventory model for LSC and LEAP devices";

    augment "/nt:network-topology/nt:topology/nt:topology-types" {
        container leap-topology {
            presence "The presence of the container node indicates a network of LEAP
                        devices";
        }
    }

    typedef protocol-type {
        description "Type of protocol which is the source of node count data.";
        type enumeration {
            enum ALL ;
            enum LSC;
            enum LEAP;
        }
    }

    grouping unified-topology {
        container unified-network-topology {
            list unified-topology {
                key "topology-id";

                leaf topology-id {
                    type string;
                    description "Id of the topology. NETCONF- topology-netconf, Openflow- flow:1,
                                        LEAP- leap-topology, etc";
                }

                list nodes {
                    key "node-id";
                    leaf node-id {
                        type string;
                        description "Unique id of the node/device";
                    }

                    leaf node-reference {
                        type instance-identifier;
                        description "A type for an absolute reference to a node instance. (This type
                                                should not be used for relative references. In such a case, a
                                                relative path should be used instead.)";
                    }

                    uses ldk-db:device-args {
                        when "../node-id = leap-topology";
                    }
                }
            }
        }
    }

    rpc get-topology {
        input {
            leaf topology-id {
		description "Type of protocol which is the source of node count data.";
                type protocol-type;
            }
        }
        output {
            uses unified-topology;
        }
    }
}
